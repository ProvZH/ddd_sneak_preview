FME workspace voorbeeld_cbs.fmw
Title: Voorbeeld CBS
Description: Het doel van deze workspace is om te demonstreren hoe je:
* een dataset van het CBS kunt inlezen met behulp van de WFS,
* een dataset van het CBS kunt inlezen via de OData Feed,
* de combinatie van deze twee datasets kunt filteren op de provinciegrens.
History: 19-11-2018,Willy Tadema,

Parameters:
- DestDataset_GEOJSON = C:\temp\git\ddd_sneak_preview\data\energieverbruik_particuliere_woningen_2017_per_buurt.geojson   # Destination GeoJSON File
- DestDataset_TDE = C:\temp\git\ddd_sneak_preview\data   # Destination Tableau TDE Directory
- SourceDataset_WFS = https://geodata.nationaalgeoregister.nl/bestuurlijkegrenzen/wfs?   # Source WFS (Web Feature Service) URL
- SourceDataset_OData = https://opendata.cbs.nl/ODataFeed/odata/84314NED/TypedDataSet   # Source OData URL

Readers:
- WFS_1: WFS from $(SourceDataset_WFS)

Writers:
- GEOJSON_1: GEOJSON to $(DestDataset_GEOJSON)
- TDE_1: TDE to $(DestDataset_TDE)

Note: Inlezen van CBS-dataset 84314NED (Energieverbruik particuliere woningen 2017) voor alle buurten in de provincie Zuid-Holland
Note: OData reader werkt in dit geval niet, vandaar de workaround. / Zie https://knowledge.safe.com/questions/59276/importing-odata-feed-with-https-url.html
InlineQuerier
    QUERY_DEF:
      energieleveringen_per_buurt_pzh,SELECT b."buurtcode", b."buurtnaam", b."gemeentecode", b."gemeentenaam", b."wijkcode", b."fme_feature_content",
      e."ID", e."Woningkenmerken", e."WijkenEnBuurten", e."Gemeentenaam", e."SoortRegio", e."Codering",
      e."GemiddeldAardgasverbruik_m3", e."GemiddeldElektriciteitsverbruik_kWh", e."Stadsverwarming_perc",
      e."IndelingswijzigingWijkenEnBuurten", e."Woningkenmerken_label"
      FROM buurten b
      INNER JOIN energieleveringen e
      ON b."buurtcode" = e."Codering"
      ,FIRST
    TABLE_DEF = buurten,buurtcode,varchar(200),buurtnaam,varchar(200),gemeentecode,varchar(200),gemeentenaam,varchar(200),wijkcode,varchar(200),energieleveringen,ID,varchar(200),Woningkenmerken,varchar(200),WijkenEnBuurten,varchar(200),Gemeentenaam,varchar(200),SoortRegio,varchar(200),Codering,varchar(200),GemiddeldAardgasverbruik_m3,varchar(200),GemiddeldElektriciteitsverbruik_kWh,varchar(200),Stadsverwarming_perc,varchar(200),IndelingswijzigingWijkenEnBuurten,varchar(200),Woningkenmerken_label,varchar(200)
    QUERY_SCHEMA = energieleveringen_per_buurt_pzh,buurtcode,varchar(200),buurtnaam,varchar(200),gemeentecode,varchar(200),gemeentenaam,varchar(200),wijkcode,varchar(200),buurten.fme_feature_content,fme_feature_content,ID,varchar(200),Woningkenmerken,varchar(200),WijkenEnBuurten,varchar(200),Gemeentenaam,varchar(200),SoortRegio,varchar(200),Codering,varchar(200),GemiddeldAardgasverbruik_m3,varchar(200),GemiddeldElektriciteitsverbruik_kWh,varchar(200),Stadsverwarming_perc,varchar(200),IndelingswijzigingWijkenEnBuurten,varchar(200),Woningkenmerken_label,varchar(200)
    energieleveringen_per_buurt_pzh -> Reprojector
Reprojector
    SOURCE = Read from feature
    DEST = EPSG:4326
    INTERPOLATION_TYPE_NAME = Nearest Neighbor
    RASTER_CELL_SIZE = Preserve Cells
    REPROJECTED -> energieverbruik (writer GEOJSON_1)
    REPROJECTED -> energieverbruik (writer TDE_1)
Note: GeoJSON
energieverbruik (writer GEOJSON_1)
    attributes: buurtcode string, buurtnaam string, gemeentecode string, gemeentenaam string, wijkcode string, ID string, Woningkenmerken string, WijkenEnBuurten string, Gemeentenaam string, SoortRegio string, Codering string, GemiddeldAardgasverbruik_m3 string, GemiddeldElektriciteitsverbruik_kWh string, Stadsverwarming_perc string, IndelingswijzigingWijkenEnBuurten string, Woningkenmerken_label string
Note: Tableau
energieverbruik (writer TDE_1)
    attributes: buurtcode charstring, buurtnaam charstring, gemeentecode charstring, gemeentenaam charstring, wijkcode charstring, ID charstring, Woningkenmerken charstring, WijkenEnBuurten charstring, Gemeentenaam charstring, SoortRegio charstring, Codering charstring, GemiddeldAardgasverbruik_m3 charstring, GemiddeldElektriciteitsverbruik_kWh charstring, Stadsverwarming_perc charstring, IndelingswijzigingWijkenEnBuurten charstring, Woningkenmerken_label charstring

Bookmark: Provinciegrens met een kleine buffer
provincies (reader WFS_1)
    attributes: gml_parent_id xml_buffer, gml_parent_property xml_buffer, gml_id xml_buffer, gid xml_int32, gid.xsi_nil xml_boolean, provincienaam xml_buffer, provincienaam.xsi_nil xml_boolean, geom xml_geometry
    -> Bufferer
Bufferer
    CAP_STYLE = Round
    CORNER_STYLE = Round
    ANGLE = 22.5
    OFFSET = 100
    BUFFERED -> FeatureReader [INITIATOR]

Bookmark: Buurten in de provincie Zuid-Holland
FeatureReader
    WFS_CONNECTION_TIMEOUT = 90
    WFS_USE_OLD_READER = NO
    WFS_MAP_GEOMETRY_COLUMNS = YES
    INTERACT = Contains
    DATASET = https://geodata.nationaalgeoregister.nl/wijkenbuurten2017/wfs?&request=GetCapabilities&service=WFS
    FORMAT = WFS
    WFS_PREFER_POST = No
    FEATURETYPES = cbs_buurten_2017
    WFS_MAP_PREDEFINED_GML_PROPERTIES = NO
    WFS_LOCAL_CACHE_EXPIRY = 60
    OUTPUT_FEATURES_DISPLAY = Schema and Data Features
    WFS_USE_SEARCH_ENVELOPE = NO
    WFS_TRANSFER_TIMEOUT = 90
    WFS_XML_FRAGMENTS_AS_DOCUMENTS = YES
    WFS_PREFERRED_VERSION = 1.0.0
    WFS_DISABLE_XML_NAMESPACE_PROCESSING = NO
    WFS_MAP_COMPLEX_PROPERTIES_AS = Nested Attributes
    ATTRIBUTES = cbs_buurten_2017,"gml_parent_id,gml_parent_property,gml_id,aantal_inwoners,aantal_inwoners.xsi_nil,mannen,mannen.xsi_nil,vrouwen,vrouwen.xsi_nil,aantal_huishoudens,aantal_huishoudens.xsi_nil,bevolkingsdichtheid_inwoners_per_km2,bevolkingsdichtheid_inwoners_per_km2.xsi_nil,buurtcode,buurtcode.xsi_nil,buurtnaam,buurtnaam.xsi_nil,dekkingspercentage,dekkingspercentage.xsi_nil,gemiddelde_huishoudsgrootte,gemiddelde_huishoudsgrootte.xsi_nil,gemeentecode,gemeentecode.xsi_nil,gemeentenaam,gemeentenaam.xsi_nil,indelingswijziging_wijken_en_buurten_indicator,indelingswijziging_wijken_en_buurten_indicator.xsi_nil,omgevingsadressendichtheid,omgevingsadressendichtheid.xsi_nil,oppervlakte_land_in_ha,oppervlakte_land_in_ha.xsi_nil,oppervlakte_totaal_in_ha,oppervlakte_totaal_in_ha.xsi_nil,oppervlakte_water_in_ha,oppervlakte_water_in_ha.xsi_nil,percentage_personen_0_tot_15_jaar,percentage_personen_0_tot_15_jaar.xsi_nil,percentage_personen_15_tot_25_jaar,percentage_personen_15_tot_25_jaar.xsi_nil,percentage_personen_25_tot_45_jaar,percentage_personen_25_tot_45_jaar.xsi_nil,percentage_personen_45_tot_65_jaar,percentage_personen_45_tot_65_jaar.xsi_nil,percentage_personen_65_jaar_en_ouder,percentage_personen_65_jaar_en_ouder.xsi_nil,percentage_uit_nederlandse_antillen_en_aruba,percentage_uit_nederlandse_antillen_en_aruba.xsi_nil,percentage_eenpersoonshuishoudens,percentage_eenpersoonshuishoudens.xsi_nil,percentage_gehuwd,percentage_gehuwd.xsi_nil,percentage_gescheid,percentage_gescheid.xsi_nil,percentage_huishoudens_met_kinderen,percentage_huishoudens_met_kinderen.xsi_nil,percentage_huishoudens_zonder_kinderen,percentage_huishoudens_zonder_kinderen.xsi_nil,percentage_uit_marokko,percentage_uit_marokko.xsi_nil,percentage_niet_westerse_allochtonen,percentage_niet_westerse_allochtonen.xsi_nil,percentage_ongehuwd,percentage_ongehuwd.xsi_nil,percentage_overige_niet_westerse_allochtonen,percentage_overige_niet_westerse_allochtonen.xsi_nil,percentage_uit_suriname,percentage_uit_suriname.xsi_nil,percentage_uit_turkije,percentage_uit_turkije.xsi_nil,percentage_verweduwd,percentage_verweduwd.xsi_nil,percentage_westerse_allochtonen,percentage_westerse_allochtonen.xsi_nil,meest_voorkomende_postcode,meest_voorkomende_postcode.xsi_nil,stedelijkheid_adressen_per_km2,stedelijkheid_adressen_per_km2.xsi_nil,water,water.xsi_nil,wijkcode,wijkcode.xsi_nil,geom,fme_geometry{0}"
    WFS_DISABLE_AUTOMATIC_READER_TYPE_SELECTION = NO
    WFS_FLATTEN_XML_FRAGMENTS = NO
    ATTR_ACCUM_MODE = Only Use Result
    WFS_IGNORE_APPLICATON_SCHEMA = no
    WFS_PREFER_DATASET_URL = No
    WFS_MAP_EMBEDDED_OBJECTS_AS = ATTRIBUTES
    WFS_ENFORCE_PATH_CONTINUITY_BY = SNAPPING_END_POINTS
    COMBINE_GEOM = Use Result
    cbs_buurten_2017 -> AttributeKeeper_2
AttributeKeeper_2
    KEEP_ATTRS = gemeentenaam,wijkcode,buurtnaam,buurtcode,gemeentecode
    -> InlineQuerier [buurten]

Bookmark: Aantal requests dat nodig is om de hele dataset op te vragen
Creator
    NUM = 1
    GEOMTYPE = Geometry Object
    CREATED -> HTTPCaller
HTTPCaller
    ERROR_ATTR = _error
    TRANSFER_TIMEOUT_LENGTH = 90
    SAVE_FILE = Attribute
    VERIFY_SSL_CERTIFICATES = No
    STATUS_CODE_ATTR = _http_status_code
    TARGET_ATTR = count
    CONNECTION_TIMEOUT_LENGTH = 60
    TARGET_ATTR_ENCODING = auto-detect
    FOLLOW_REDIRECTS = Yes
    TARGET_URL = $(SourceDataset_OData)/$count
    USE_COOKIES = No
    RESPONSE_HEADER_LIST_ATTR = _headers
    HTTP_METHOD = GET
    -> Cloner
Cloner
    COPIES = @ceil(@Evaluate(@Value(count) / 10000))
    COPYATT = number
    COPY -> AttributeCreator

Bookmark: Datasets inlezen
AttributeCreator
    ATTR_TABLE = SET_TO request = FME_CONDITIONAL:DEFAULT_VALUE'$(SourceDataset_OData)?$format=json&$skip=@Evaluate(@Value(number)*10000)'BOOL_OP;OR;COMPOSITE_TEST;<Unused>;TEST @Value(number) = 0'$(SourceDataset_OData)?$format=json'FME_NUM_CONDITIONS2___
    -> HTTPCaller_2
HTTPCaller_2
    ERROR_ATTR = _error
    TRANSFER_TIMEOUT_LENGTH = 90
    SAVE_FILE = Attribute
    VERIFY_SSL_CERTIFICATES = No
    STATUS_CODE_ATTR = _http_status_code
    TARGET_ATTR = _response_body
    CONNECTION_TIMEOUT_LENGTH = 60
    TARGET_ATTR_ENCODING = auto-detect
    FOLLOW_REDIRECTS = Yes
    TARGET_URL = @Value(request)
    USE_COOKIES = No
    RESPONSE_HEADER_LIST_ATTR = _headers
    HTTP_METHOD = GET
    -> JSONFragmenter
JSONFragmenter
    RECURSIVE = Yes
    JSON_ATTR = _response_body
    NEW_ATTRIBUTES = ID Woningkenmerken WijkenEnBuurten Gemeentenaam_1 SoortRegio_2 Codering_3 GemiddeldAardgasverbruik_4 GemiddeldElektriciteitsverbruik_5 Stadsverwarming_6 IndelingswijzigingWijkenEnBuurten_7
    EXTRACT_ATTR = Yes
    EXPLODE_FORMAT = JSON
    JSON_QUERY = json["value"][*]
    FRAGMENTS -> AttributeManager
AttributeManager
    ATTR_TABLE:
      REMOVE request
      REMOVE _creation_instance
      REMOVE _headers{}.name
      REMOVE _headers{}.value
      REMOVE count
      REMOVE _http_status_code
      REMOVE number
      REMOVE _response_body
      REMOVE json_type
      REMOVE json_index
      RENAME_SET_VALUE Gemeentenaam_1 > Gemeentenaam
      RENAME_SET_VALUE SoortRegio_2 > SoortRegio
      RENAME_SET_VALUE Codering_3 > Codering
      RENAME_SET_VALUE GemiddeldAardgasverbruik_4 > GemiddeldAardgasverbruik_m3
      RENAME_SET_VALUE GemiddeldElektriciteitsverbruik_5 > GemiddeldElektriciteitsverbruik_kWh
      RENAME_SET_VALUE Stadsverwarming_6 > Stadsverwarming_perc
      RENAME_SET_VALUE IndelingswijzigingWijkenEnBuurten_7 > IndelingswijzigingWijkenEnBuurten
    -> AttributeValueMapper
AttributeValueMapper
    VAL_ATTR = Woningkenmerken_label
    LUT = a,Totaal woningen,b,Appartement,c,Tussenwoning,d,Hoekwoning,e,Twee-onder-één-kap woning,f,Vrijstaande woning,g,Eigen woning,h,Huurwoning
    SRC = Woningkenmerken
    DIRECTION = Forward (Source To Destination)
    -> InlineQuerier [energieleveringen]
